module topologyappcomplete {
    yang-version 1.1;
    namespace "it:nextworks:yang:topologyappcomplete";
    prefix "topologyappcomplete";

//    import ietf-yang-types { prefix "yang"; }
//    import ietf-inet-types { prefix "inet"; }
    import tapi-topology { prefix "tapi-topology"; }

    revision "2020-05-14" {
        description "Initial revision of topologyappcomplete model";
    }

    rpc add-static-topology {
        input {
            container topology {
                uses tapi-topology:topology;
            }
       }
    }

    rpc remove-static-topology {
        input {
            leaf topology {
                type string;
            }
       }
    }
}
